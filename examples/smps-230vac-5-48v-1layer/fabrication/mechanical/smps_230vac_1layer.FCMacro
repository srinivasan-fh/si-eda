# SiEDA board "SMPS 230 VAC to 5-48 V 5 A (CC/CV)" for FreeCAD (generated by SiEDA).
# Run it with Macro > Macros... > Execute.
# It builds the board and one box per part, named by designator. Move or turn parts (flat on their side),
# then run it again in that design: it writes SMPS_230_VAC_to_5-48_V_5_A__CC_CV_-placement.emn, which SiEDA reads with
# File > Import MCAD Placement (IDF).
import os
import FreeCAD as App
import Part

NAME = "SMPS_230_VAC_to_5-48_V_5_A__CC_CV_"
THICKNESS = 1.6
OUTLINE = [(0., 0.), (270., 0.), (270., -176.), (0., -176.)]
CUTOUTS = []
HOLES = [(265.5, -4.5, 3.2), (4.5, -171.5, 3.2), (135., -4.5, 3.2), (135., -171.5, 3.2), (265.5, -135.384615, 3.2)]
# (designator, x, y, IDF rotation, bottom side, body box x0, y0, x1, y1, height above the board, height)
PARTS = [
    ("J1", 6.75, -24.37, 0, True, 2.94, -31.99, 10.56, -16.75, 0., 8.),
    ("F1", 35.1, -10.83, 0, True, 20.6, -15.33, 49.6, -6.33, 0., 1.),
    ("RV1", 68.85, -10.83, 0, True, 62.1, -13.33, 75.6, -8.33, 0., 14.),
    ("CX1", 33.75, -25.72, 0, True, 23.25, -28.22, 44.25, -23.22, 0., 14.),
    ("LF1", 25.65, -56.86, 0, True, 14.15, -68.36, 37.15, -45.36, 0., 1.),
    ("CX2", 56.7, -41.97, 270, True, 54.2, -52.47, 59.2, -31.47, 0., 14.),
    ("CY2", 71.55, -29.78, 270, True, 70.3, -32.28, 72.8, -27.28, 0., 6.),
    ("CY3", 71.55, -48.74, 270, True, 70.3, -51.24, 72.8, -46.24, 0., 6.),
    ("BR1", 40.5, -82.58, 0, True, 31.28, -84.18, 49.72, -80.98, 0., 1.),
    ("RT1", 70.2, -70.4, 270, True, 68.95, -73.55, 71.45, -67.25, 0., 2.5),
    ("CIN1", 70.2, -85.29, 0, True, 67.7, -86.54, 72.7, -84.04, 0., 6.),
    ("U1", 83.7, -117.55, 270, False, 78.955, -119.5, 88.445, -115.6, 0., 1.5),
    ("LPFC", 32.4, -129.97, 0, True, 15.4, -145.47, 49.4, -114.47, 0., 1.),
    ("Q1", 72.9, -159.75, 0, True, 66.8675, -162., 78.9325, -157.5, 0., 1.),
    ("DPFC", 94.5, -159.75, 0, True, 89.5, -162., 99.5, -157.5, 0., 15.),
    ("CB1", 126.9, -140.8, 0, True, 111.9, -155.8, 141.9, -125.8, 0., 1.),
    ("R1", 120.3, -100.95, 90, False, 119.5, -102.55, 121.1, -99.35, 0., 0.55),
    ("R2", 84.43, -103.21, 0, False, 82.83, -104.01, 86.03, -102.41, 0., 0.55),
    ("R3", 114.88, -92.03, 0, False, 113.88, -92.655, 115.88, -91.405, 0., 0.5),
    ("C1", 72.36, -117.62, 270, False, 71.735, -118.62, 72.985, -116.62, 0., 1.),
    ("R4", 52.65, -94.09, 0, False, 51.05, -94.89, 54.25, -93.29, 0., 0.55),
    ("R5", 78.03, -86.35, 270, False, 77.23, -87.95, 78.83, -84.75, 0., 0.55),
    ("R6", 114.88, -98.67, 0, False, 113.88, -99.295, 115.88, -98.045, 0., 0.5),
    ("C2", 77.08, -144.63, 0, False, 76.08, -145.255, 78.08, -144.005, 0., 1.),
    ("C3", 113.94, -105.3, 0, False, 112.94, -105.925, 114.94, -104.675, 0., 1.),
    ("R7", 105.43, -92.03, 0, False, 104.43, -92.655, 106.43, -91.405, 0., 0.5),
    ("R8", 72.36, -136.1, 0, False, 71.36, -136.725, 73.36, -135.475, 0., 0.5),
    ("R9", 122.85, -108.98, 270, False, 122.05, -110.58, 123.65, -107.38, 0., 0.55),
    ("R10", 95.98, -112.89, 270, False, 95.18, -114.49, 96.78, -111.29, 0., 0.55),
    ("R15", 105.43, -98.67, 0, False, 104.43, -99.295, 106.43, -98.045, 0., 0.5),
    ("R16", 70.47, -141.79, 270, False, 69.845, -142.79, 71.095, -140.79, 0., 0.5),
    ("R17", 112.99, -111.94, 0, False, 111.99, -112.565, 113.99, -111.315, 0., 0.5),
    ("R11", 86.53, -140.37, 0, False, 85.53, -140.995, 87.53, -139.745, 0., 0.5),
    ("R12", 88.43, -147.95, 270, False, 87.805, -148.95, 89.055, -146.95, 0., 0.5),
    ("R13", 105.3, -95.45, 0, False, 103.7, -96.25, 106.9, -94.65, 0., 0.55),
    ("R14", 80.34, -140.37, 0, False, 79.34, -140.995, 81.34, -139.745, 0., 0.5),
    ("C4", 82.76, -146.06, 270, False, 82.135, -147.06, 83.385, -145.06, 0., 1.),
    ("U2", 113.4, -37.91, 0, True, 110.24, -42.99, 116.56, -32.83, 0., 3.5),
    ("Q2", 129.6, -75.82, 0, True, 123.5675, -78.07, 135.6325, -73.57, 0., 1.),
    ("T1", 163.35, -40.62, 180, True, 140.35, -60.62, 186.35, -20.62, 0., 1.),
    ("DOUT", 202.5, -16.25, 0, True, 197.5, -18.5, 207.5, -14., 0., 15.),
    ("DSN", 143.1, -79.88, 270, True, 141.75, -82.48, 144.45, -77.28, 0., 2.7),
    ("R20", 115.42, -56.86, 0, True, 112.27, -58.11, 118.57, -55.61, 0., 2.5),
    ("C5", 110.03, -48.06, 0, True, 107.53, -49.31, 112.53, -46.81, 0., 6.),
    ("R18", 130.95, -88., 270, False, 130.15, -89.6, 131.75, -86.4, 0., 0.55),
    ("R19", 126.9, -68.37, 0, False, 125.9, -68.995, 127.9, -67.745, 0., 0.5),
    ("R21", 116.78, -79.88, 270, False, 116.155, -80.88, 117.405, -78.88, 0., 0.5),
    ("C6", 112.05, -70.4, 270, False, 111.425, -71.4, 112.675, -69.4, 0., 1.),
    ("R22", 118.12, -50.77, 270, False, 117.495, -51.77, 118.745, -49.77, 0., 0.5),
    ("C7", 108., -63.63, 270, False, 107.375, -64.63, 108.625, -62.63, 0., 1.),
    ("C8", 118.12, -88., 270, False, 117.495, -89., 118.745, -87., 0., 1.),
    ("DAUX", 126.9, -56.18, 270, True, 125.55, -58.78, 128.25, -53.58, 0., 2.7),
    ("C9", 92.47, -84.62, 270, True, 89.32, -87.77, 95.62, -81.47, 0., 11.),
    ("U6", 105.97, -77.85, 0, True, 100.97, -80.1, 110.97, -75.6, 0., 15.),
    ("C10", 112.05, -88., 270, False, 111.25, -89.6, 112.85, -86.4, 0., 1.2),
    ("R23", 120.83, -27.75, 0, True, 117.68, -29., 123.98, -26.5, 0., 2.5),
    ("C11", 226.8, -18.95, 0, True, 220.3, -25.45, 233.3, -12.45, 0., 1.),
    ("C12", 248.4, -18.95, 0, True, 241.9, -25.45, 254.9, -12.45, 0., 1.),
    ("U3", 163.35, -77.17, 0, True, 160.19, -79.71, 166.51, -74.63, 0., 3.5),
    ("U4", 202.5, -62.28, 0, False, 201.05, -63.08, 203.95, -61.48, 0., 1.1),
    ("R24", 213.38, -41.2, 0, False, 212.38, -41.825, 214.38, -40.575, 0., 0.5),
    ("R25", 215.32, -35.2, 0, False, 214.32, -35.825, 216.32, -34.575, 0., 0.5),
    ("R26", 222.41, -35.2, 90, False, 221.785, -36.2, 223.035, -34.2, 0., 0.5),
    ("R27", 216.34, -39.26, 270, False, 215.715, -40.26, 216.965, -38.26, 0., 0.5),
    ("R28", 219.38, -31.14, 0, False, 218.38, -31.765, 220.38, -30.515, 0., 0.5),
    ("C13", 220.39, -39.26, 0, False, 219.39, -39.885, 221.39, -38.635, 0., 1.),
    ("DB", 206.55, -54.15, 0, True, 203.95, -55.5, 209.15, -52.8, 0., 2.7),
    ("C14", 229.84, -35.2, 270, True, 226.69, -38.35, 232.99, -32.05, 0., 11.),
    ("U7", 224.1, -54.15, 0, True, 219.1, -56.4, 229.1, -51.9, 0., 15.),
    ("C15", 213.3, -31.82, 0, False, 211.7, -32.62, 214.9, -31.02, 0., 1.2),
    ("CY1", 163.35, -124.55, 180, True, 156.35, -127.55, 170.35, -121.55, 0., 1.),
    ("U5", 184.95, -140.8, 0, True, 181.79, -145.88, 188.11, -135.72, 0., 3.5),
    ("U8", 187.65, -97.48, 0, True, 184.49, -102.56, 190.81, -92.4, 0., 3.5),
    ("Q3", 205.2, -92.06, 0, False, 201.875, -94.265, 208.525, -89.855, 0., 1.),
    ("Q4", 205.2, -111.02, 0, False, 201.875, -113.225, 208.525, -108.815, 0., 1.),
    ("LB", 236.25, -102.89, 0, True, 223.75, -115.39, 248.75, -90.39, 0., 1.),
    ("R29", 198.45, -98.83, 0, False, 197.45, -99.455, 199.45, -98.205, 0., 0.5),
    ("R30", 193.05, -108.98, 270, False, 192.425, -109.98, 193.675, -107.98, 0., 0.5),
    ("R31", 186.97, -108.98, 0, False, 185.97, -109.605, 187.97, -108.355, 0., 0.5),
    ("DBST", 199.8, -103.57, 0, False, 198.45, -104.37, 201.15, -102.77, 0., 1.1),
    ("C16", 205.2, -98.83, 0, False, 204.2, -99.455, 206.2, -98.205, 0., 1.),
    ("C17", 214.65, -104.92, 270, False, 214.025, -105.92, 215.275, -103.92, 0., 1.),
    ("C18", 226.8, -140.8, 0, True, 220.3, -147.3, 233.3, -134.3, 0., 1.),
    ("C19", 248.4, -140.8, 0, True, 241.9, -147.3, 254.9, -134.3, 0., 1.),
    ("C20", 213.97, -117.78, 0, False, 212.37, -118.58, 215.57, -116.98, 0., 1.2),
    ("J2", 263.25, -162.46, 0, True, 259.44, -167.54, 267.06, -157.38, 0., 8.),
    ("R32", 251.1, -165.17, 270, False, 250.3, -166.77, 251.9, -163.57, 0., 0.55),
    ("NT1", 251.1, -159.08, 0, False, 249.15, -160.015, 253.05, -158.145, 0., 1.5),
    ("NT2", 251.1, -171.26, 0, False, 249.15, -172.195, 253.05, -170.325, 0., 1.5),
    ("C21", 214.65, -110.34, 0, False, 213.65, -110.965, 215.65, -109.715, 0., 1.),
    ("R33", 180.22, -124.55, 270, False, 179.595, -125.55, 180.845, -123.55, 0., 0.5),
    ("C22", 181.57, -115.75, 0, False, 180.57, -116.375, 182.57, -115.125, 0., 1.),
    ("R34", 181.57, -111.02, 0, False, 180.57, -111.645, 182.57, -110.395, 0., 0.5),
    ("U9", 216., -162.46, 0, False, 214.05, -165.3, 217.95, -159.62, 0., 1.5),
    ("DCV", 196.43, -140.8, 0, False, 195.08, -141.6, 197.78, -140., 0., 1.1),
    ("DCC", 196.43, -136.06, 0, False, 195.08, -136.86, 197.78, -135.26, 0., 1.1),
    ("R35", 212.62, -134.03, 270, False, 211.995, -135.03, 213.245, -133.03, 0., 0.5),
    ("R36", 212.62, -127.94, 0, False, 211.62, -128.565, 213.62, -127.315, 0., 0.5),
    ("C23", 207.22, -148.92, 0, False, 206.22, -149.545, 208.22, -148.295, 0., 1.),
    ("C24", 220.72, -155.02, 0, False, 219.72, -155.645, 221.72, -154.395, 0., 1.),
    ("R37", 224.1, -162.46, 270, False, 223.475, -163.46, 224.725, -161.46, 0., 0.5),
    ("U10", 240.3, -165.17, 0, False, 238.85, -165.97, 241.75, -164.37, 0., 1.1),
    ("C25", 226.12, -123.2, 0, False, 225.12, -123.825, 227.12, -122.575, 0., 1.),
    ("J3", 263.25, -86.65, 0, True, 261.98, -91.73, 264.52, -81.57, 0., 2.5),
    ("R38", 215.32, -123.2, 0, False, 214.32, -123.825, 216.32, -122.575, 0., 0.5),
    ("R39", 220.72, -124.55, 270, False, 220.095, -125.55, 221.345, -123.55, 0., 0.5),
    ("C26", 204.53, -117.78, 0, False, 203.53, -118.405, 205.53, -117.155, 0., 1.),
    ("C27", 211.95, -99.51, 0, False, 210.95, -100.135, 212.95, -98.885, 0., 1.),
    ("C28", 205.2, -122.52, 0, False, 204.2, -123.145, 206.2, -121.895, 0., 1.),
    ("DPWR", 197.78, -121.17, 0, False, 196.78, -121.795, 198.78, -120.545, 0., 0.8),
    ("R40", 197.1, -115.75, 270, False, 196.475, -116.75, 197.725, -114.75, 0., 0.5),
    ("MH1", 6.08, -6.09, 0, True, 3.08, -9.09, 9.08, -3.09, 0., 1.),
    ("JW1", 119.75, -82.125, 270, True, 119.45, -103.5, 120.05, -60.75, 0., 0.6),
    ("JW2", 121.25, -43.375, 270, True, 120.95, -49., 121.55, -37.75, 0., 0.6),
    ("JW3", 113.655647, -55.75801, 0, True, 107., -60.75, 120.311293, -50.766021, 0., 0.6),
    ("JW4", 215.5, -77.625, 270, True, 215.2, -94.75, 215.8, -60.5, 0., 0.6),
    ("JW5", 218.25, -35.625, 0, True, 214., -39., 222.5, -32.25, 0., 0.6),
    ("JW6", 217.880469, -60.772906, 0, True, 209.75, -88.5, 226.010938, -33.045813, 0., 0.6),
    ("JW7", 198.875, -119.625, 0, True, 194., -124.5, 203.75, -114.75, 0., 0.6),
    ("JW8", 236.5, -147.875, 270, True, 236.2, -161., 236.8, -134.75, 0., 0.6),
    ("JW9", 214.5, -80.125, 270, True, 214., -97.5, 215., -62.75, 0., 0.6),
    ("JW10", 216., -114., 0, True, 215.25, -115.5, 216.75, -112.5, 0., 0.6),
    ("JW11", 224.5, -122.25, 0, True, 223.25, -123.5, 225.75, -121., 0., 0.6),
    ("JW12", 204.25, -120.5, 0, True, 202.75, -120.8, 205.75, -120.2, 0., 0.6),
    ("JW13", 196.785236, -129.513117, 0, True, 192.75, -138., 200.820472, -121.026235, 0., 0.6),
    ("JW14", 197.25, -107., 270, True, 195.25, -109., 199.25, -105., 0., 0.6),
    ("JW15", 179.75, -120.5, 270, True, 179.45, -133., 180.05, -108., 0., 0.6),
    ("JW16", 187.5, -107.125, 270, True, 185., -109., 190., -105.25, 0., 0.6),
    ("JW17", 205.125, -48., 0, True, 197.75, -58.75, 212.5, -37.25, 0., 0.6),
    ("JW18", 209.367031, -50.911939, 0, True, 198.984063, -60.323877, 219.75, -41.5, 0., 0.6),
    ("JW19", 201.25, -100.25, 270, True, 199., -103.75, 203.5, -96.75, 0., 0.6),
    ("JW20", 217.375, -54.125, 0, True, 217., -63.5, 217.75, -44.75, 0., 0.6),
    ("JW21", 204.375, -55.25, 0, True, 196.25, -75.5, 212.5, -35., 0., 0.6),
    ("JW22", 183.25, -108., 270, True, 180.25, -111., 186.25, -105., 0., 0.6),
    ("JW23", 38.5, -45.875, 270, True, 37.5, -54., 39.5, -37.75, 0., 0.6),
    ("JW24", 202.375, -97.125, 0, True, 201.5, -98.5, 203.25, -95.75, 0., 0.6),
    ("JW25", 130.125, -43.875, 270, True, 122.25, -54.25, 138., -33.5, 0., 0.6),
    ("JW26", 151., -67.5, 270, True, 150.7, -72., 151.3, -63., 0., 0.6),
    ("JW27", 203.125, -93.875, 270, True, 200.5, -96.75, 205.75, -91., 0., 0.6),
    ("JW28", 206.807527, -102.4861, 0, True, 206., -107.5, 207.615054, -97.4722, 0., 0.6),
    ("JW29", 218.25, -114.75, 270, True, 210., -118., 226.5, -111.5, 0., 0.6),
    ("JW30", 75.125, -80.25, 0, True, 74.25, -89.25, 76., -71.25, 0., 0.6),
    ("JW31", 51.625, -64.625, 0, True, 38.75, -77.5, 64.5, -51.75, 0., 0.6),
    ("JW32", 62.925396, -44.020123, 270, True, 61.75, -49.790247, 64.100791, -38.25, 0., 0.6),
    ("JW33", 214., -109.875, 0, True, 210., -116.75, 218., -103., 0., 0.6),
    ("JW34", 210., -124.625, 270, True, 209.7, -130.5, 210.3, -118.75, 0., 0.6),
    ("JW35", 239., -139., 0, True, 238.5, -141., 239.5, -137., 0., 0.6),
    ("JW36", 58.125, -142.125, 270, True, 52.5, -147.75, 63.75, -136.5, 0., 0.6),
    ("JW37", 199.125, -108.625, 0, True, 195.75, -109.75, 202.5, -107.5, 0., 0.6),
    ("JW38", 235., -164.25, 270, True, 232.5, -166.75, 237.5, -161.75, 0., 0.6),
    ("JW39", 71.625, -151.625, 0, True, 69., -154.25, 74.25, -149., 0., 0.6),
    ("JW40", 78.125, -90.5, 0, True, 75.75, -93.5, 80.5, -87.5, 0., 0.6),
    ("JW41", 178., -120.875, 270, True, 177.7, -123.5, 178.3, -118.25, 0., 0.6),
    ("JW42", 210., -144.375, 270, True, 209.7, -151., 210.3, -137.75, 0., 0.6),
    ("JW43", 176.25, -129.375, 270, True, 175.95, -143.25, 176.55, -115.5, 0., 0.6),
    ("JW44", 130.75, -45.875, 270, True, 130.45, -57.25, 131.05, -34.5, 0., 0.6),
    ("JW45", 78.625, -145.875, 270, True, 71.75, -147., 85.5, -144.75, 0., 0.6),
    ("JW46", 109.875, -66.25, 270, True, 105.5, -68.25, 114.25, -64.25, 0., 0.6),
    ("JW47", 207., -61.25, 270, True, 206.7, -62.75, 207.3, -59.75, 0., 0.6),
    ("JW48", 212.375, -68.125, 270, True, 212.075, -70.25, 212.675, -66., 0., 0.6),
    ("JW49", 110.75, -68.875, 270, True, 106.5, -70.25, 115., -67.5, 0., 0.6),
    ("JW50", 115., -78., 270, True, 114.7, -83.75, 115.3, -72.25, 0., 0.6),
    ("JW51", 128.125, -62.125, 0, True, 124., -70.25, 132.25, -54., 0., 0.6),
    ("JW52", 146.375, -62.5, 270, True, 138., -63., 154.75, -62., 0., 0.6),
    ("JW53", 131.618451, -72.862211, 0, True, 126.25, -82., 136.986902, -63.724422, 0., 0.6),
    ("JW54", 108.375, -84.375, 0, True, 106.5, -86.25, 110.25, -82.5, 0., 0.6),
    ("JW55", 217.875, -140.125, 0, True, 217.25, -158.25, 218.5, -122., 0., 0.6),
    ("JW56", 226.330403, -119.579694, 0, True, 220.410805, -121.409387, 232.25, -117.75, 0., 0.6),
    ("JW57", 213.375, -144.625, 0, True, 211., -161.75, 215.75, -127.5, 0., 0.6),
    ("JW58", 216.025, -126.375, 270, True, 213.5, -127.5, 218.55, -125.25, 0., 0.6),
    ("JW59", 228.625, -125.875, 0, True, 227., -127.5, 230.25, -124.25, 0., 0.6),
    ("JW60", 30.125, -36.875, 0, True, 24., -43., 36.25, -30.75, 0., 0.6),
    ("JW61", 190.5, -74.25, 0, True, 186.25, -78.5, 194.75, -70., 0., 0.6),
    ("JW62", 194.75, -57.125, 270, True, 194.45, -68., 195.05, -46.25, 0., 0.6),
    ("JW63", 217.25, -29., 0, True, 215., -29.3, 219.5, -28.7, 0., 0.6),
    ("JW64", 245.125, -165.875, 0, True, 242.75, -168.25, 247.5, -163.5, 0., 0.6),
    ("JW65", 115.125, -108.625, 0, True, 114., -109.75, 116.25, -107.5, 0., 0.6),
    ("JW66", 125.75, -34.375, 0, True, 122.25, -35.75, 129.25, -33., 0., 0.6),
    ("JW67", 126.25, -123.25, 0, True, 122.75, -123.55, 129.75, -122.95, 0., 0.6),
    ("JW68", 106.375, -99.625, 270, True, 101.75, -104.25, 111., -95., 0., 0.6),
    ("JW69", 81.25, -129.625, 270, True, 80.95, -133.75, 81.55, -125.5, 0., 0.6),
    ("JW70", 83.625, -125.625, 0, True, 83.25, -138.25, 84., -113., 0., 0.6),
    ("JW71", 76.875, -123.625, 0, True, 72.75, -134., 81., -113.25, 0., 0.6),
    ("JW72", 85.875, -114.625, 0, True, 79.5, -114.925, 92.25, -114.325, 0., 0.6),
    ("JW73", 97.717635, -107.336515, 0, True, 93.93527, -113.423029, 101.5, -101.25, 0., 0.6),
    ("JW74", 73.375, -136.75, 0, True, 72.5, -141., 74.25, -132.5, 0., 0.6),
    ("JW75", 86.66786, -128.765596, 0, True, 75.83572, -131.281193, 97.5, -126.25, 0., 0.6),
    ("JW76", 86.625, -140.25, 0, True, 84.5, -143.25, 88.75, -137.25, 0., 0.6),
    ("JW77", 79.507943, -141.129437, 270, True, 75.5, -141.508874, 83.515885, -140.75, 0., 0.6),
    ("JW78", 106.125, -104., 0, True, 97.75, -119.75, 114.5, -88.25, 0., 0.6),
    ("JW79", 103.125, -82., 270, True, 98.5, -82.5, 107.75, -81.5, 0., 0.6),
    ("JW80", 104., -57.75, 270, True, 103.7, -73.25, 104.3, -42.25, 0., 0.6),
    ("JW81", 90.75, -104.875, 270, True, 90.45, -109., 91.05, -100.75, 0., 0.6),
    ("JW82", 99.115987, -100.453481, 270, True, 92.231974, -101.5, 106., -99.406961, 0., 0.6),
    ("JW83", 82.761139, -125.476411, 0, True, 73.25, -143.25, 92.272278, -107.702822, 0., 0.6),
    ("JW84", 82.375, -152.875, 270, True, 81.5, -163.25, 83.25, -142.5, 0., 0.6),
    ("JW85", 84.883222, -138.997029, 0, True, 79.516444, -142.244057, 90.25, -135.75, 0., 0.6),
    ("JW86", 88.875, -122.875, 270, True, 88.575, -132.5, 89.175, -113.25, 0., 0.6),
    ("JW87", 112.125, -99.375, 270, True, 106.25, -108.75, 118., -90., 0., 0.6),
    ("JW88", 98.5, -96.5, 0, True, 88.5, -100.75, 108.5, -92.25, 0., 0.6),
]
IDF_HEADER = ['.HEADER', 'BOARD_FILE 3.0 "FreeCAD" 2026/01/01.00:00:00 1', '"%s" MM' % NAME, '.END_HEADER', '.PLACEMENT']

def face(points):
    pts = [App.Vector(x, y, 0) for x, y in points]
    return Part.Face(Part.makePolygon(pts + pts[:1]))


def build():
    doc = App.newDocument(NAME)
    board = face(OUTLINE).extrude(App.Vector(0, 0, THICKNESS))
    for cut in CUTOUTS:
        board = board.cut(face(cut).extrude(App.Vector(0, 0, THICKNESS)))
    for x, y, d in HOLES:
        board = board.cut(Part.makeCylinder(d / 2, THICKNESS, App.Vector(x, y, 0)))
    doc.addObject("Part::Feature", "Board").Shape = board
    for ref, x, y, rot, bottom, x0, y0, x1, y1, z0, h in PARTS:
        part = doc.addObject("Part::Feature", "Part")
        part.Label = ref
        part.Shape = Part.makeBox(x1 - x0, y1 - y0, h, App.Vector(x0 - x, y0 - y, 0))
        part.Placement = App.Placement(App.Vector(x, y, -z0 - h if bottom else THICKNESS + z0), App.Rotation())
        part.addProperty("App::PropertyString", "SiedaRef", "SiEDA").SiedaRef = ref
        part.addProperty("App::PropertyFloat", "SiedaRotation", "SiEDA").SiedaRotation = rot
        part.addProperty("App::PropertyBool", "SiedaBottom", "SiEDA").SiedaBottom = bottom
    doc.recompute()


def send_back(doc):
    lines = list(IDF_HEADER)
    for part in doc.Objects:
        if hasattr(part, "SiedaRef"):
            p = part.Placement
            angle = (part.SiedaRotation + p.Rotation.toEuler()[0]) % 360
            lines.append('"PART" "PART" "%s"' % part.SiedaRef)
            lines.append("%.4f %.4f 0 %.2f %s PLACED" % (p.Base.x, p.Base.y, angle, "BOTTOM" if part.SiedaBottom else "TOP"))
    lines.append(".END_PLACEMENT")
    folder = os.path.dirname(doc.FileName) if doc.FileName else os.path.expanduser("~")
    path = os.path.join(folder, NAME + "-placement.emn")
    with open(path, "w") as f:
        f.write("\n".join(lines) + "\n")
    App.Console.PrintMessage("SiEDA placement written to %s\n" % path)


doc = App.ActiveDocument
if doc is not None and any(hasattr(o, "SiedaRef") for o in doc.Objects):
    send_back(doc)
else:
    build()
