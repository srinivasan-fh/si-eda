# SiEDA board "SMPS 230 VAC to 5-48 V 5 A (CC/CV)" for FreeCAD (generated by SiEDA).
# Run it with Macro > Macros... > Execute.
# It builds the board and one box per part, named by designator. Move or turn parts (flat on their side),
# then run it again in that design: it writes SMPS_230_VAC_to_5-48_V_5_A__CC_CV_-placement.emn, which SiEDA reads with
# File > Import MCAD Placement (IDF).
import os
import FreeCAD as App
import Part

NAME = "SMPS_230_VAC_to_5-48_V_5_A__CC_CV_"
THICKNESS = 1.6
OUTLINE = [(0., 0.), (200., 0.), (200., -130.), (0., -130.)]
CUTOUTS = []
HOLES = [(195.5, -4.5, 3.2), (4.5, -125.5, 3.2), (100., -4.5, 3.2), (100., -125.5, 3.2), (195.5, -100., 3.2)]
# (designator, x, y, IDF rotation, bottom side, body box x0, y0, x1, y1, height above the board, height)
PARTS = [
    ("J1", 5., -18., 0, False, 1.19, -25.62, 8.81, -10.38, 0., 8.),
    ("F1", 26., -8., 0, False, 11.5, -12.5, 40.5, -3.5, 0., 1.),
    ("RV1", 51., -8., 0, False, 44.25, -10.5, 57.75, -5.5, 0., 14.),
    ("CX1", 25., -19., 0, False, 14.5, -21.5, 35.5, -16.5, 0., 14.),
    ("LF1", 19., -42., 0, False, 7.5, -53.5, 30.5, -30.5, 0., 1.),
    ("CX2", 42., -31., 270, False, 39.5, -41.5, 44.5, -20.5, 0., 14.),
    ("CY2", 53., -22., 270, False, 51.75, -24.5, 54.25, -19.5, 0., 6.),
    ("CY3", 53., -36., 270, False, 51.75, -38.5, 54.25, -33.5, 0., 6.),
    ("BR1", 30., -61., 0, False, 20.78, -62.6, 39.22, -59.4, 0., 1.),
    ("RT1", 52., -52., 270, False, 50.75, -55.15, 53.25, -48.85, 0., 2.5),
    ("CIN1", 52., -63., 0, False, 49.5, -64.25, 54.5, -61.75, 0., 6.),
    ("U1", 62., -92., 0, False, 60.05, -96.745, 63.95, -87.255, 0., 1.5),
    ("LPFC", 24., -96., 0, False, 7., -111.5, 41., -80.5, 0., 1.),
    ("Q1", 54., -118., 0, False, 47.9675, -120.25, 60.0325, -115.75, 0., 1.),
    ("DPFC", 70., -118., 0, False, 65., -120.25, 75., -115.75, 0., 15.),
    ("CB1", 94., -104., 0, False, 79., -119., 109., -89., 0., 1.),
    ("R1", 86.5, -79., 270, False, 85.7, -80.6, 87.3, -77.4, 0., 0.55),
    ("R2", 64.5, -82., 270, False, 63.7, -83.6, 65.3, -80.4, 0., 0.55),
    ("R3", 78.5, -74., 0, False, 77.5, -74.625, 79.5, -73.375, 0., 0.5),
    ("C1", 56., -87.5, 270, False, 55.375, -88.5, 56.625, -86.5, 0., 1.),
    ("R4", 39., -69.5, 0, False, 37.4, -70.3, 40.6, -68.7, 0., 0.55),
    ("R5", 59., -71., 270, False, 58.2, -72.6, 59.8, -69.4, 0., 0.55),
    ("R6", 78.5, -77.5, 0, False, 77.5, -78.125, 79.5, -76.875, 0., 0.5),
    ("C2", 58.5, -101.75, 0, False, 57.5, -102.375, 59.5, -101.125, 0., 1.),
    ("C3", 78., -81., 0, False, 77., -81.625, 79., -80.375, 0., 1.),
    ("R7", 73.5, -74., 0, False, 72.5, -74.625, 74.5, -73.375, 0., 0.5),
    ("R8", 56., -97.25, 0, False, 55., -97.875, 57., -96.625, 0., 0.5),
    ("R9", 91., -80.5, 270, False, 90.2, -82.1, 91.8, -78.9, 0., 0.55),
    ("R10", 68.5, -85., 270, False, 67.7, -86.6, 69.3, -83.4, 0., 0.55),
    ("R15", 73.5, -77.5, 0, False, 72.5, -78.125, 74.5, -76.875, 0., 0.5),
    ("R16", 55., -100.25, 270, False, 54.375, -101.25, 55.625, -99.25, 0., 0.5),
    ("R17", 77.5, -84.5, 0, False, 76.5, -85.125, 78.5, -83.875, 0., 0.5),
    ("R11", 63.5, -99.5, 0, False, 62.5, -100.125, 64.5, -98.875, 0., 0.5),
    ("R12", 64.5, -103.5, 270, False, 63.875, -104.5, 65.125, -102.5, 0., 0.5),
    ("R13", 78., -70.5, 0, False, 76.4, -71.3, 79.6, -69.7, 0., 0.55),
    ("R14", 58., -99.5, 0, False, 57., -100.125, 59., -98.875, 0., 0.5),
    ("C4", 61.5, -102.5, 270, False, 60.875, -103.5, 62.125, -101.5, 0., 1.),
    ("U2", 84., -28., 0, False, 80.84, -33.08, 87.16, -22.92, 0., 3.5),
    ("Q2", 96., -56., 0, False, 89.9675, -58.25, 102.0325, -53.75, 0., 1.),
    ("T1", 121., -30., 0, False, 98., -50., 144., -10., 0., 1.),
    ("DOUT", 150., -12., 0, False, 145., -14.25, 155., -9.75, 0., 15.),
    ("DSN", 106., -59., 270, False, 104.65, -61.6, 107.35, -56.4, 0., 2.7),
    ("R20", 85.5, -42., 0, False, 82.35, -43.25, 88.65, -40.75, 0., 2.5),
    ("C5", 81.5, -35.5, 0, False, 79., -36.75, 84., -34.25, 0., 6.),
    ("R18", 97., -65., 270, False, 96.2, -66.6, 97.8, -63.4, 0., 0.55),
    ("R19", 94., -50.5, 0, False, 93., -51.125, 95., -49.875, 0., 0.5),
    ("R21", 86.5, -59., 270, False, 85.875, -60., 87.125, -58., 0., 0.5),
    ("C6", 83., -52., 270, False, 82.375, -53., 83.625, -51., 0., 1.),
    ("R22", 87.5, -37.5, 270, False, 86.875, -38.5, 88.125, -36.5, 0., 0.5),
    ("C7", 80., -47., 270, False, 79.375, -48., 80.625, -46., 0., 1.),
    ("C8", 87.5, -65., 270, False, 86.875, -66., 88.125, -64., 0., 1.),
    ("DAUX", 94., -41.5, 270, False, 92.65, -44.1, 95.35, -38.9, 0., 2.7),
    ("C9", 68.5, -62.5, 270, False, 65.35, -65.65, 71.65, -59.35, 0., 11.),
    ("U6", 78.5, -57.5, 0, False, 73.5, -59.75, 83.5, -55.25, 0., 15.),
    ("C10", 83., -65., 270, False, 82.2, -66.6, 83.8, -63.4, 0., 1.2),
    ("R23", 89.5, -20.5, 0, False, 86.35, -21.75, 92.65, -19.25, 0., 2.5),
    ("C11", 168., -14., 0, False, 161.5, -20.5, 174.5, -7.5, 0., 1.),
    ("C12", 184., -14., 0, False, 177.5, -20.5, 190.5, -7.5, 0., 1.),
    ("U3", 121., -57., 180, False, 117.84, -59.54, 124.16, -54.46, 0., 3.5),
    ("U4", 150., -46., 0, False, 148.55, -46.8, 151.45, -45.2, 0., 1.1),
    ("R24", 162.5, -26., 270, False, 161.875, -27., 163.125, -25., 0., 0.5),
    ("R25", 159.5, -26., 0, False, 158.5, -26.625, 160.5, -25.375, 0., 0.5),
    ("R26", 164.75, -26., 270, False, 164.125, -27., 165.375, -25., 0., 0.5),
    ("R27", 160.25, -29., 270, False, 159.625, -30., 160.875, -28., 0., 0.5),
    ("R28", 162.5, -23., 0, False, 161.5, -23.625, 163.5, -22.375, 0., 0.5),
    ("C13", 163.25, -29., 0, False, 162.25, -29.625, 164.25, -28.375, 0., 1.),
    ("DB", 153., -40., 0, False, 150.4, -41.35, 155.6, -38.65, 0., 2.7),
    ("C14", 170.25, -26., 270, False, 167.1, -29.15, 173.4, -22.85, 0., 11.),
    ("U7", 166., -40., 0, False, 161., -42.25, 171., -37.75, 0., 15.),
    ("C15", 158., -23.5, 0, False, 156.4, -24.3, 159.6, -22.7, 0., 1.2),
    ("CY1", 121., -92., 0, False, 114., -95., 128., -89., 0., 1.),
    ("U5", 137., -104., 0, False, 133.84, -109.08, 140.16, -98.92, 0., 3.5),
    ("U8", 139., -72., 0, False, 135.84, -77.08, 142.16, -66.92, 0., 3.5),
    ("Q3", 152., -68., 0, False, 148.675, -70.205, 155.325, -65.795, 0., 1.),
    ("Q4", 152., -82., 0, False, 148.675, -84.205, 155.325, -79.795, 0., 1.),
    ("LB", 175., -76., 0, False, 162.5, -88.5, 187.5, -63.5, 0., 1.),
    ("R29", 147., -73., 0, False, 146., -73.625, 148., -72.375, 0., 0.5),
    ("R30", 143., -80.5, 270, False, 142.375, -81.5, 143.625, -79.5, 0., 0.5),
    ("R31", 138.5, -80.5, 270, False, 137.875, -81.5, 139.125, -79.5, 0., 0.5),
    ("DBST", 148., -76.5, 0, False, 146.65, -77.3, 149.35, -75.7, 0., 1.1),
    ("C16", 152., -73., 0, False, 151., -73.625, 153., -72.375, 0., 1.),
    ("C17", 159., -77.5, 270, False, 158.375, -78.5, 159.625, -76.5, 0., 1.),
    ("C18", 168., -104., 0, False, 161.5, -110.5, 174.5, -97.5, 0., 1.),
    ("C19", 184., -104., 0, False, 177.5, -110.5, 190.5, -97.5, 0., 1.),
    ("C20", 158.5, -87., 0, False, 156.9, -87.8, 160.1, -86.2, 0., 1.2),
    ("J2", 195., -120., 0, False, 191.19, -125.08, 198.81, -114.92, 0., 8.),
    ("R32", 186., -122., 270, False, 185.2, -123.6, 186.8, -120.4, 0., 0.55),
    ("NT1", 186., -117.5, 0, False, 184.05, -118.435, 187.95, -116.565, 0., 1.5),
    ("NT2", 186., -126.5, 0, False, 184.05, -127.435, 187.95, -125.565, 0., 1.5),
    ("C21", 159., -81.5, 0, False, 158., -82.125, 160., -80.875, 0., 1.),
    ("R33", 133.5, -92., 270, False, 132.875, -93., 134.125, -91., 0., 0.5),
    ("C22", 134.5, -85.5, 0, False, 133.5, -86.125, 135.5, -84.875, 0., 1.),
    ("R34", 134.5, -82., 0, False, 133.5, -82.625, 135.5, -81.375, 0., 0.5),
    ("U9", 160., -120., 0, False, 158.05, -122.84, 161.95, -117.16, 0., 1.5),
    ("DCV", 145.5, -104., 0, False, 144.15, -104.8, 146.85, -103.2, 0., 1.1),
    ("DCC", 145.5, -100.5, 0, False, 144.15, -101.3, 146.85, -99.7, 0., 1.1),
    ("R35", 157.5, -99., 270, False, 156.875, -100., 158.125, -98., 0., 0.5),
    ("R36", 157.5, -94.5, 0, False, 156.5, -95.125, 158.5, -93.875, 0., 0.5),
    ("C23", 153.5, -110., 0, False, 152.5, -110.625, 154.5, -109.375, 0., 1.),
    ("C24", 163.5, -114.5, 0, False, 162.5, -115.125, 164.5, -113.875, 0., 1.),
    ("R37", 166., -120., 270, False, 165.375, -121., 166.625, -119., 0., 0.5),
    ("U10", 178., -122., 0, False, 176.55, -122.8, 179.45, -121.2, 0., 1.1),
    ("C25", 167.5, -91., 0, False, 166.5, -91.625, 168.5, -90.375, 0., 1.),
    ("J3", 195., -64., 0, False, 193.73, -69.08, 196.27, -58.92, 0., 2.5),
    ("R38", 159.5, -91., 0, False, 158.5, -91.625, 160.5, -90.375, 0., 0.5),
    ("R39", 163.5, -92., 270, False, 162.875, -93., 164.125, -91., 0., 0.5),
    ("C26", 151.5, -87., 0, False, 150.5, -87.625, 152.5, -86.375, 0., 1.),
    ("C27", 157., -73.5, 0, False, 156., -74.125, 158., -72.875, 0., 1.),
    ("C28", 152., -90.5, 0, False, 151., -91.125, 153., -89.875, 0., 1.),
    ("DPWR", 146.5, -89.5, 0, False, 145.5, -90.125, 147.5, -88.875, 0., 0.8),
    ("R40", 146., -85.5, 270, False, 145.375, -86.5, 146.625, -84.5, 0., 0.5),
    ("MH1", 4.5, -4.5, 0, False, 1.5, -7.5, 7.5, -1.5, 0., 1.),
]
IDF_HEADER = ['.HEADER', 'BOARD_FILE 3.0 "FreeCAD" 2026/01/01.00:00:00 1', '"%s" MM' % NAME, '.END_HEADER', '.PLACEMENT']

def face(points):
    pts = [App.Vector(x, y, 0) for x, y in points]
    return Part.Face(Part.makePolygon(pts + pts[:1]))


def build():
    doc = App.newDocument(NAME)
    board = face(OUTLINE).extrude(App.Vector(0, 0, THICKNESS))
    for cut in CUTOUTS:
        board = board.cut(face(cut).extrude(App.Vector(0, 0, THICKNESS)))
    for x, y, d in HOLES:
        board = board.cut(Part.makeCylinder(d / 2, THICKNESS, App.Vector(x, y, 0)))
    doc.addObject("Part::Feature", "Board").Shape = board
    for ref, x, y, rot, bottom, x0, y0, x1, y1, z0, h in PARTS:
        part = doc.addObject("Part::Feature", "Part")
        part.Label = ref
        part.Shape = Part.makeBox(x1 - x0, y1 - y0, h, App.Vector(x0 - x, y0 - y, 0))
        part.Placement = App.Placement(App.Vector(x, y, -z0 - h if bottom else THICKNESS + z0), App.Rotation())
        part.addProperty("App::PropertyString", "SiedaRef", "SiEDA").SiedaRef = ref
        part.addProperty("App::PropertyFloat", "SiedaRotation", "SiEDA").SiedaRotation = rot
        part.addProperty("App::PropertyBool", "SiedaBottom", "SiEDA").SiedaBottom = bottom
    doc.recompute()


def send_back(doc):
    lines = list(IDF_HEADER)
    for part in doc.Objects:
        if hasattr(part, "SiedaRef"):
            p = part.Placement
            angle = (part.SiedaRotation + p.Rotation.toEuler()[0]) % 360
            lines.append('"PART" "PART" "%s"' % part.SiedaRef)
            lines.append("%.4f %.4f 0 %.2f %s PLACED" % (p.Base.x, p.Base.y, angle, "BOTTOM" if part.SiedaBottom else "TOP"))
    lines.append(".END_PLACEMENT")
    folder = os.path.dirname(doc.FileName) if doc.FileName else os.path.expanduser("~")
    path = os.path.join(folder, NAME + "-placement.emn")
    with open(path, "w") as f:
        f.write("\n".join(lines) + "\n")
    App.Console.PrintMessage("SiEDA placement written to %s\n" % path)


doc = App.ActiveDocument
if doc is not None and any(hasattr(o, "SiedaRef") for o in doc.Objects):
    send_back(doc)
else:
    build()
